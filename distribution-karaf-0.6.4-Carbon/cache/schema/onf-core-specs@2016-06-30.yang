/*
 * Copyright (c) 2016 Cisco Systems, Inc. All rights reserved.
 *
 * This program and the accompanying materials are made available under the
 * terms of the Eclipse Public License v1.0 which accompanies this distribution,
 * and is available at http://www.eclipse.org/legal/epl-v10.html INTERNAL
 */
module onf-core-specs {
  namespace "urn:onf:core-specs";
  prefix onf-cs;

  import network-topology {
    prefix nt;
  }

  revision 2016-06-30 {
  }

  grouping ltp-ref {
    leaf topology {
      type nt:topology-ref;
    }
    leaf node {
      type nt:node-ref;
    }
    leaf tp {
      type nt:tp-ref;
    }
  }

  grouping G_FcSpec {
    status current;
    leaf uuid {
      type string;
    }
    list fcPortSpec {
      key 'uuid';
      config true;
      ordered-by system;
      uses G_FcPortSetSpec;
    }
  }

  grouping G_FcPortSetSpec {
    status current;
    leaf uuid {
      type string;
    }
    list ingressFcPortSet {
      ordered-by system;
      key 'topology node tp';
      config true;
      uses ltp-ref;
    }
    list egressFcPortSet {
      ordered-by system;
      key 'topology node tp';
      config true;
      uses ltp-ref;
    }
    leaf role {
      type string;
      default true;
    }
  }

  grouping G_LtpSpec {
  }

  grouping G_LayerProtocolSpec {
    container adapterSpec {
      config true;
      uses G_ConnectionPointAndAdapterSpec;
    }
    container terminationSpec {
      config true;
      uses G_TerminationSpec;
    }
    list adapterPropertySpecList {
      key 'uuid';
      config true;
      leaf uuid {
        type string;
      }
      ordered-by system;
      uses G_AdapterPropertySpec;
    }
    container providerViewSpec {
      config true;
      uses G_ProviderViewSpec;
    }
    list serverSpecList {
      key 'uuid';
      config true;
      leaf uuid {
        type string;
      }
      ordered-by system;
      uses G_ServerSpec;
    }
  }

  grouping G_TerminationSpec {
  }

  grouping G_ConnectionPointAndAdapterSpec {
  }

  grouping G_AdapterPropertySpec {
  }

  grouping G_ProviderViewSpec {
  }

  grouping G_ServerSpec {
  }
}
