module opendaylight-topology-inventory {
    yang-version 1;
    namespace "urn:opendaylight:model:topology:inventory";
    // replace with IANA namespace when assigned
    prefix "nt";

    import yang-ext { prefix "ext"; }
    import ietf-inet-types { prefix "inet"; }
    import opendaylight-inventory {prefix "inv";}
    import opendaylight-topology {prefix "odt";}
    import network-topology {prefix "topo"; revision-date "2013-10-21"; }

    organization "TBD";

    contact "WILL-BE-DEFINED-LATER";

    revision 2013-10-30 {
        description
            "Initial revision.";
    }

    augment "/topo:network-topology/topo:topology/topo:node" {
        ext:augment-identifier "inventory-node";
        leaf inventory-node-ref {
            type inv:node-ref;
        }
    }

    augment "/topo:network-topology/topo:topology/topo:node/topo:termination-point" {
        ext:augment-identifier "inventory-node-connector";
        leaf inventory-node-connector-ref {
            ext:context-reference "inv:node-connector-context";
            type inv:node-connector-ref;
        }
    }
}
