/*
 * Copyright (c) 2016 Intel Corporation.  All rights reserved.
 *
 * This program and the accompanying materials are made available under the
 * terms of the Eclipse Public License v1.0 which accompanies this distribution,
 * and is available at http://www.eclipse.org/legal/epl-v10.html
 */
module neutron-types {

    yang-version 1;

    namespace "urn:opendaylight:neutron-types";

    prefix neutron-types;

    import ietf-inet-types { prefix "inet"; revision-date 2013-07-15; }

    organization "OpenDaylight Neutron Group";

    contact "Isaku Yamahata <isaku.yamahata@gmail.com>";

    description "This YANG module defines common typedefs for Openstack Neutron";

    revision "2016-05-17" {
        description
                "OpenDaylight Boron release";
    }

    typedef ip-prefix-or-address {
        description "ip prefix or ip address";
        type union {
            type inet:ip-prefix;
            type inet:ip-address;
        }
    }
}
