/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-L3-ext {

    yang-version 1;

    namespace "urn:opendaylight:neutron-L3-ext";

    prefix neutron-L3-ext;

    import neutron { prefix "neutron"; }
    import yang-ext { prefix "ext"; }

    organization "OpenDaylight Neutron Group";

    contact "J. Gregory Hall <ghall@brocade.com>, Kiran Sreenivasa <kkoushik@brocade.com>";

    description "This YANG module defines Openstack Neutron L3 model extensions";
    revision "2015-07-12" {
        description
                "OpenDaylight Beryllium release";
    }

    augment "/neutron:neutron/neutron:networks/neutron:network"{
        description "This module augments the networks container
                in the neutron-networks module with router information.";
        ext:augment-identifier "network-l3-extension";
        leaf external {
            description "If true, it indicates that the router is externally accessible.";
            type boolean;
            default "false";
        }
    }
}
