module openflow-plugin-provider-impl {
	yang-version 1;
    namespace "urn:opendaylight:params:xml:ns:yang:config:openflow:plugin:impl";
    prefix "openflow-plugin-provider-impl";

    import config {prefix config; revision-date 2013-04-05;}
    import rpc-context { prefix rpcx; revision-date 2013-06-17; }
    import openflow-provider {prefix openflow-provider; revision-date 2015-03-31;}
    import openflow-switch-connection-provider {prefix openflow-switch-connection-provider;revision-date 2014-03-28;}
    import opendaylight-md-sal-binding { prefix md-sal-binding; revision-date 2013-10-28;}
    import opendaylight-sal-binding-broker-impl { prefix sal-broker; revision-date 2013-10-28;}
    import openflowplugin-extension-registry {prefix ofp-ext-reg; revision-date 2015-04-25;}
    import opendaylight-entity-ownership-service { prefix ownership-service; revision-date 2015-08-10;}

    description
        "openflow-plugin-impl";

    revision "2015-03-27" {
        description
            "Second openflow plugin implementation.";
    }

    typedef non-zero-uint32-type {
        type uint32 {
            range "1..max";
        }
    }

    typedef non-zero-uint16-type {
        type uint16 {
            range "1..max";
        }
     }

    identity openflow-plugin-provider-impl {
        base config:module-type;
        config:provided-service openflow-provider:openflow-provider;
        config:provided-service ofp-ext-reg:openflow-extension-registry-provider;
        config:java-name-prefix OpenFlowProvider;
    }

    augment "/config:modules/config:module/config:configuration" {
        case openflow-plugin-provider-impl {
            when "/config:modules/config:module/config:type = 'openflow-plugin-provider-impl'";

            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-adapter {
                uses config:service-ref {
                    refine type {
                        mandatory true;
                        config:required-identity sal-broker:binding-new-notification-service;
                    }
                }
            }
            container notification-publish-adapter {
                uses config:service-ref {
                    refine type {
                        mandatory true;
                        config:required-identity sal-broker:binding-new-notification-publish-service;
                    }
                }
            }
            container entity-ownership-service {
                uses config:service-ref {
                    refine type {
                        mandatory true;
                        config:required-identity ownership-service:entity-ownership-service;
                    }
                }
            }
            list openflow-switch-connection-provider {
                uses config:service-ref {
                    refine type {
                        mandatory true;
                        config:required-identity openflow-switch-connection-provider:openflow-switch-connection-provider;
                    }
                }
            }
            leaf rpc-requests-quota {
                type uint32;
                default 500;
            }
            leaf switch-features-mandatory {
                type boolean;
                default false;
            }
            leaf global-notification-quota {
                type uint32;
                default 131072;
            }
            leaf is-statistics-polling-on {
                type boolean;
                default "true";
            }
            leaf is-statistics-rpc-enabled {
                status deprecated;
                description "Exposing backward compatible statistics rpcs providing result in form of async notification";
                type boolean;
                default "false";
            }
            leaf barrier-interval-timeout-limit {
                type non-zero-uint32-type;
                default 500;
            }
            leaf barrier-count-limit {
                type non-zero-uint16-type;
                default 25600;
            }
            leaf echo-reply-timeout {
                type non-zero-uint32-type;
                default 2000;
            }
        }

    }
}
