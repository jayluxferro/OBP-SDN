module sal-experimenter-message {
    namespace "urn:opendaylight:experimenter-message:service";
    prefix exp-msg;

    import opendaylight-inventory {prefix inv; revision-date "2013-08-19";}
    import openflowplugin-experimenter-types {prefix exp-type; revision-date "2015-10-20";}

    description "Openflow experimenter (symmetric) message service and notification.";

    revision "2015-10-20" {
        description "Initial revision of experimenter message service";
    }

    grouping experimenter-symmetric-message {
        description "Experimenter message with node and xid reference included.";
        uses "inv:node-context-ref";
        uses exp-type:experimenter-core-message;
    }

    rpc send-experimenter {
        description "Send experimenter request to device, expecting reply.";
        input {
            uses "inv:node-context-ref";
            uses exp-type:experimenter-core-message;
        }
    }

    notification experimenter-message-from-dev {
        description "Upon experimenter request message received.";
        uses experimenter-symmetric-message;
    }

}
