/*
 * Copyright (c) 2016 Intel Corporation.  All rights reserved.
 *
 * This program and the accompanying materials are made available under the
 * terms of the Eclipse Public License v1.0 which accompanies this distribution,
 * and is available at http://www.eclipse.org/legal/epl-v10.html
 */

module neutron-portsecurity {

    yang-version 1;

    namespace "urn:opendaylight:neutron-portsecurity";

    prefix neutron-portsecurity;

    import yang-ext { prefix "ext"; }
    import neutron { prefix "neutron"; }


    organization "OpenDaylight Neutron Group";

    contact "Dileep Ranganathan <dileep.ranganathan@intel.com>";

    description "This YANG module defines port-security attributes that are used
        by OpenDaylight Neutron YANG modules.";

    revision "2015-07-12" {
        description
                "OpenDaylight Beryllium release";
    }

    augment "/neutron:neutron/neutron:ports/neutron:port" {
        description "This module augments the ports container in
                the neutron-ports module with port-security information.";
        ext:augment-identifier "port-security-extension";
        leaf port-security-enabled {
            type boolean;
            description "The port security status. The status is enabled (true) or disabled (false).";
        }
    }
}
