module neutron-constants {

    yang-version 1;

    namespace "urn:opendaylight:neutron-constants";

    prefix neutron-constants;

    organization "OpenDaylight Neutron Group";

    contact "Ryan Moats <rmoats@us.ibm.com>";

    revision "2015-07-12" {
        description "Initial revision";
    }

    // PROTOCOL
    identity protocol-base {
        description "Base identity for all front end protocols";
    }

    identity protocol-http {
        description "HTTP protocol.";
        base protocol-base;
    }

    identity protocol-terminated-https {
        description "TERMINATED HTTPS protocol.";
        base protocol-base;
    }

    identity protocol-https {
        description "HTTPS protocol.";
        base protocol-base;
    }

    identity protocol-tcp {
        description "TCP protocol.";
        base protocol-base;
    }

    identity protocol-icmp {
        description "ICMP protocol.";
        base protocol-base;
    }

    identity protocol-icmp-v6 {
        description "ICMPV6 protocol.";
        base protocol-base;
    }

    identity protocol-udp {
        description "UDP protocol.";
        base protocol-base;
    }

    // PROBE
    identity probe-base {
        description "Base identity for all probes";
    }

    identity probe-http {
        description "HTTP protocol.";
        base probe-base;
    }

    identity probe-https {
        description "HTTPS protocol.";
        base probe-base;
    }

    identity probe-tcp {
        description "TCP protocol.";
        base probe-base;
    }

    identity probe-ping {
        description "PING protocol.";
        base probe-base;
    }

    // FWaaS v1
    identity fw-protocol-base {
        description "Base identity for firewall protocol";
    }

    identity fw-protocol-tcp {
        description "TCP protocol.";
        base fw-protocol-base;
    }

    identity fw-protocol-udp {
        description "UDP protocol.";
        base fw-protocol-base;
    }

    identity fw-protocol-icmp {
        description "ICMP protocol.";
        base fw-protocol-base;
    }

    // DIRECTION
    identity direction-base {
        description "Base identity for direction";
    }

    identity direction-ingress {
        description "Ingress direction.";
        base direction-base;
    }

    identity direction-egress {
        description "Egress direction.";
        base direction-base;

    }

    // IP VERSION
    identity ip-version-base {
        description "the base identity for ip versions";
    }

    identity ip-version-v4 {
        description "IP v4";
        base ip-version-base;
    }

    identity ip-version-v6 {
        description "IP v6";
        base ip-version-base;
    }

    // ETHERTYPE
    identity ethertype-base {
        description "the base identity for ethertype versions";
    }

    identity ethertype-v4 {
        description "IP v4";
        base ethertype-base;
    }

    identity ethertype-v6 {
        description "IP v6";
        base ethertype-base;
    }

    // DHCP
    identity dhcpv6-base {
        description "the base identity for DHCP v6 information";
    }

    identity dhcpv6-off {
        description "DHCP v6 off";
        base dhcpv6-base;
    }

    identity dhcpv6-stateful {
        description "DHCP v6 stateful";
        base dhcpv6-base;
    }

    identity dhcpv6-slaac {
        description "SLAAC";
        base dhcpv6-base;
    }

    identity dhcpv6-stateless {
        description "DHCP v6 stateless";
        base dhcpv6-base;
    }
}
