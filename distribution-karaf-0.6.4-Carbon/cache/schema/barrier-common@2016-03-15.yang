module barrier-common {
    namespace "urn:opendaylight:service:barrier:common";
    prefix barrier-common;

    description "Openflow barrier for services - common groupings.";

    revision "2016-03-15" {
        description "Initial revision of batch common groupings.";
    }

    grouping barrier-suffix {
        description "Flag indicating that barrier will be attached after some service-specific action.";

        leaf barrier-after {
            type boolean;
        }
    }
}
