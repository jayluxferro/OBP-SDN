module interface-service-bindings {
    namespace "urn:opendaylight:genius:interfacemanager:servicebinding";
    prefix ifservicebindings;

    import opendaylight-flow-types {prefix offlow;revision-date "2013-10-26";}
    import openflowplugin-extension-nicira-action {
        prefix ofplugin;
        revision-date "2014-07-14";
    }

    import yang-ext {
        prefix ext;
    }

    import ietf-interfaces {
        prefix if; revision-date 2014-05-08;
    }

    revision "2016-04-06" {
        description "This YANG module defines the service binding model.";
    }

    identity service-type-base {
       description "Base identity for all service-types";
    }

    identity service-type-flow-based {
       description "Service type for flow-based services";
       base service-type-base;
    }

    identity service-mode-base {
       description "Base identity for all service-modes";
    }

    identity service-mode-ingress {
       description "Service mode for ingress binding services.
           Ingress binding services get applied to all packets ingressing the switch.
           e.g. egress ACLs applied to VM ports are considered ingress service for the switch";
       base service-mode-base;
    }

    identity service-mode-egress {
       description "Service mode for egress binding services.
           Egress binding services get applied to all packets egressing the switch.
           e.g. ingress ACLs applied to VM ports are considered egress service for the switch";
       base service-mode-base;
    }

    container service-bindings {
        list services-info {
            key "interface-name service-mode";
            leaf interface-name {
                type string;
            }

            leaf service-mode {
                type identityref{
                   base service-mode-base;
                }
            }

            list bound-services {
                key "service-priority";
                max-elements "16";
                min-elements "0";
                leaf service-priority {
                    type uint8;
                }

                leaf service-type {
                    type identityref {
                        base service-type-base;
                    }
                }

                leaf service-name {
                    type string;
                }
            }
        }
    }

    grouping service-openflow-info {
        description "openflow specific information for services info.";

        leaf dispatcher-table-id {
            type uint8;
        }

        leaf flow-priority {
            type uint16;
        }

        leaf flow-cookie {
            type uint64;
        }

        uses offlow:instruction-list;
    }

    augment "/service-bindings/services-info/bound-services" {
        ext:augment-identifier "stype-openflow";
        when "service-type = 'service-type-flow-based'";
        uses service-openflow-info;
    }

    augment "/service-bindings/services-info/bound-services/instruction/instruction/apply-actions-case/apply-actions/action/action" {
        case "service-binding-nx-action-reg-load-apply-actions-case" {
            uses ofplugin:nx-action-reg-load-grouping;
        }
    }

    augment "/service-bindings/services-info/bound-services/instruction/instruction/write-actions-case/write-actions/action/action" {
        case "service-binding-nx-action-reg-load-write-actions-case" {
            uses ofplugin:nx-action-reg-load-grouping;
        }
    }

    augment "/service-bindings/services-info/bound-services/instruction/instruction/apply-actions-case/apply-actions/action/action" {
        case "service-binding-nx-action-reg-move-apply-actions-case" {
            uses ofplugin:nx-action-reg-move-grouping;
        }
    }

    augment "/service-bindings/services-info/bound-services/instruction/instruction/write-actions-case/write-actions/action/action" {
        case "service-binding-nx-action-reg-move-write-actions-case" {
            uses ofplugin:nx-action-reg-move-grouping;
        }
    }

    augment "/service-bindings/services-info/bound-services/instruction/instruction/apply-actions-case/apply-actions/action/action" {
        case "service-binding-nx-action-output-reg-apply-actions-case" {
            uses ofplugin:nx-action-output-reg-grouping;
        }
    }

    augment "/service-bindings/services-info/bound-services/instruction/instruction/write-actions-case/write-actions/action/action" {
        case "service-binding-nx-action-output-reg-write-actions-case" {
            uses ofplugin:nx-action-output-reg-grouping;
        }
    }

    augment "/service-bindings/services-info/bound-services/instruction/instruction/apply-actions-case/apply-actions/action/action" {
        case "service-binding-nx-action-resubmit-apply-actions-case" {
            uses ofplugin:nx-action-resubmit-grouping;
        }
    }

    augment "/service-bindings/services-info/bound-services/instruction/instruction/write-actions-case/write-actions/action/action" {
        case "service-binding-nx-action-resubmit-write-actions-case" {
            uses ofplugin:nx-action-resubmit-grouping;
        }
    }

    augment "/service-bindings/services-info/bound-services/instruction/instruction/apply-actions-case/apply-actions/action/action" {
        case "service-binding-nx-action-multipath-apply-actions-case" {
            uses ofplugin:nx-action-multipath-grouping;
        }
    }

    augment "/service-bindings/services-info/bound-services/instruction/instruction/write-actions-case/write-actions/action/action" {
        case "service-binding-nx-action-multipath-write-actions-case" {
            uses ofplugin:nx-action-multipath-grouping;
        }
    }

    augment "/service-bindings/services-info/bound-services/instruction/instruction/apply-actions-case/apply-actions/action/action" {
        case "service-binding-nx-action-push-nsh-apply-actions-case" {
            uses ofplugin:nx-action-push-nsh-grouping;
        }
    }

    augment "/service-bindings/services-info/bound-services/instruction/instruction/write-actions-case/write-actions/action/action" {
        case "service-binding-nx-action-push-nsh-write-actions-case" {
            uses ofplugin:nx-action-push-nsh-grouping;
        }
    }

    augment "/service-bindings/services-info/bound-services/instruction/instruction/apply-actions-case/apply-actions/action/action" {
        case "service-binding-nx-action-pop-nsh-apply-actions-case" {
            uses ofplugin:nx-action-pop-nsh-grouping;
        }
    }

    augment "/service-bindings/services-info/bound-services/instruction/instruction/write-actions-case/write-actions/action/action" {
        case "service-binding-nx-action-pop-nsh-write-actions-case" {
            uses ofplugin:nx-action-pop-nsh-grouping;
        }
    }

    augment "/service-bindings/services-info/bound-services/instruction/instruction/apply-actions-case/apply-actions/action/action" {
        case "service-binding-nx-action-conntrack-apply-actions-case" {
            uses ofplugin:nx-action-conntrack-grouping;
        }
    }

    augment "/service-bindings/services-info/bound-services/instruction/instruction/write-actions-case/write-actions/action/action" {
        case "service-binding-nx-action-conntrack-write-actions-case" {
            uses ofplugin:nx-action-conntrack-grouping;
        }
    }

    augment "/service-bindings/services-info/bound-services/instruction/instruction/apply-actions-case/apply-actions/action/action" {
        case "service-binding-nx-action-learn-apply-actions-case" {
            uses ofplugin:nx-action-learn-grouping;
        }
    }

    augment "/service-bindings/services-info/bound-services/instruction/instruction/write-actions-case/write-actions/action/action" {
        case "service-binding-nx-action-learn-write-actions-case" {
            uses ofplugin:nx-action-learn-grouping;
        }
    }

    container bound-services-state-list {
            config false;
            description "Contains the interface-state information for bound-services";

            list bound-services-state {
                key "interface-name service-mode";
                    leaf interface-name {
                        type string;
                    }

                    leaf service-mode {
                        type identityref{
                            base service-mode-base;
                        }
                    }
                    leaf dpid {
                        type uint64;
                    }
                    leaf port-no {
                        type uint32;
                    }
                    leaf if-index {
                        type int32;
                    }
                    leaf interface-type {
                        type identityref {
                            base if:interface-type;
                        }
                    }
            }
       }
}
