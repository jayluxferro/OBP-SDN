/*
 * Copyright (c) 2016 Cisco Systems, Inc. All rights reserved.
 *
 * This program and the accompanying materials are made available under the
 * terms of the Eclipse Public License v1.0 which accompanies this distribution,
 * and is available at http://www.eclipse.org/legal/epl-v10.html INTERNAL
 */
module mef-nrp-bandwidth-profile {
  namespace "urn:mef:nrp-bandwidth-profile";
  prefix nrp-bwp;

  import mef-nrp-types {
    prefix nrp-types;
  }

  revision 2016-06-30 {
  }

  grouping G_NRP_BwpFlow {
    leaf bwpFlowIndex {
      type nrp-types:NRP_PositiveInteger;
      description "The index i=1,2,...,n is used to index the Bandwidth Profile Flow among all Bandwidth Profile
Flows that are mapped to a given Envelope";
    }
    leaf cir {
      type nrp-types:NRP_NaturalNumber;
      description "Committed Information Rate that limits the average rate of frames that will be declared
Green. In bits per second.";
    }
    leaf cirMax {
      type nrp-types:NRP_NaturalNumber;
      description "Maximum Committed Information Rate that limits the rate of tokens added to the committed token
bucket. In bits per second.";
    }
    leaf cbs {
      type nrp-types:NRP_NaturalNumber;
      description "Committed Burst Size that limits the maximum number of bytes available for a burst of frames
that will be declared Green, in bytes,";
    }
    leaf eir {
      type nrp-types:NRP_NaturalNumber;
      description "Excess Information Rate that limits the average rate of frames that will be declared Yellow, in
bits per second.";
    }
    leaf eirMax {
      type nrp-types:NRP_NaturalNumber;
      description "Maximum Excess Infor-mation Rate that Limits the rate of tokens added to the excess token
bucket, in bits per second.";
    }
    leaf ebs {
      type nrp-types:NRP_NaturalNumber;
      description "Excessive Burst Size that limits the maximum number of bytes available for a burst of frames
that will be declared Yellow, in bytes.";
    }
    leaf couplingFlag {
      type nrp-types:NRP_NaturalNumber;
      description "Coupling Flag that Determines if overflow Green tokens can be used as Yellow tokens. Value 0 for
NO and value 1 for YES.";
    }
    leaf colorMode {
      type nrp-types:NRP_ColorMode;
      description "Color Mode that Indicates whether the Color Identifier of the frame is considered by the
Bandwidth Profile Algorithm.";
    }
    leaf rank {
      type nrp-types:NRP_PositiveInteger;
      description "Bandwidth prorile flow rank in an associated Envelope.";
    }
    leaf tokenRequestOffset {
      type nrp-types:NRP_NaturalNumber;
      description "Adjusts the number of tokens requested for each external interface frame.";
    }
  }

  grouping G_NRP_ColorIdentifier {
    choice identifier {
      case sap-color-id {
        container serviceAccessPointColorId {
          uses G_NRP_ServiceAccessPointColorId;
        }
      }
      case pcp-color-id {
        container pcpColorId {
          uses G_NRP_PcpColorId;
        }
      }
      case dei-color-id {
        container deiColorId {
          uses G_NRP_DeiColorId;
        }
      }
      case desp-color-id {
        container despColorId {
          uses G_NRP_DespColorId;
        }
      }
    }
  }

  grouping G_NRP_ServiceAccessPointColorId {
    leaf color {
      type nrp-types:NRP_FrameColor;
      description "Green or Yellow.";
    }
  }
  grouping G_NRP_PcpColorId {
    leaf vlanTag {
      type nrp-types:NRP_VlanTag;
      description "Which vlan tag pcp to be used for color identier, S tag or C tag. S-tag is not valid for EvcEndPoint. ";
    }
    leaf-list pcpValue {
      description "List PCP values map to the same color.";
      ordered-by system;
      type nrp-types:NRP_NaturalNumber;
      min-elements 1;
    }
    leaf color {
      type nrp-types:NRP_FrameColor;
      description "Green or Yellow.";
    }
  }
  grouping G_NRP_DeiColorId {
    leaf vlanTag {
      type nrp-types:NRP_VlanTag;
      description "Which vlan tag pcp to be used for color identier, S tag or C tag. S-tag is not valid for EvcEndPoint. ";
    }
    leaf-list deiValue {
      description "DEI=0 or DEI=1";
      ordered-by system;
      type nrp-types:NRP_NaturalNumber;
      max-elements 2;
      min-elements 1;
    }
    leaf color {
      type nrp-types:NRP_FrameColor;
      description "Green or Yellow";
    }
  }
  grouping G_NRP_DespColorId {
    leaf ipVersion {
      type nrp-types:NRP_IpVersion;
      description "IPv4, or IPv6, or both IPv4 and IPv6.";
    }
    leaf-list dscpValue {
      description "List DSCP values map to the same color.";
      ordered-by system;
      type nrp-types:NRP_NaturalNumber;
    }
    leaf color {
      type nrp-types:NRP_FrameColor;
      description "Green or Yellow";
    }
  }

}
