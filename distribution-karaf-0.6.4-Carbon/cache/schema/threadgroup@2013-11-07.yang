// vi: set smarttab et sw=4 tabstop=4:
module threadgroup {
    yang-version 1;
    namespace "urn:opendaylight:params:xml:ns:yang:controller:netty:threadgroup";
    prefix "netty-th";

    import config { prefix config; revision-date 2013-04-05; }
    import netty { prefix netty; revision-date 2013-11-19; }

    organization "Cisco Systems, Inc.";

    contact "Robert Varga <rovarga@cisco.com>";

    description
        "This module contains the base YANG definitions for
         netty threadgroup implementation.

        Copyright (c)2013 Cisco Systems, Inc. All rights reserved.";

    revision "2013-11-07" {
        description
            "Initial revision";
    }

    identity netty-threadgroup-fixed {
        status deprecated;
        base config:module-type;
        config:provided-service netty:netty-threadgroup;
        config:java-name-prefix NettyThreadgroup;
    }

    augment "/config:modules/config:module/config:configuration" {
        case netty-threadgroup-fixed {
            when "/config:modules/config:module/config:type = 'netty-threadgroup-fixed'";

            leaf thread-count {
                status deprecated;
                type uint16;

                description "Number of threads to be used by NioEventLoopGroup. This attribute is optional and default value will be 2* Number of CPUs";
            }

            // TODO add optional thread factory dependency

        }
    }
}
