module opendaylight-multipart-types {
    namespace "urn:opendaylight:multipart:types";
    prefix multipart;

    import openflow-protocol { prefix ofproto; revision-date "2013-07-31"; }

    revision "2017-01-12" {
        description "Initial revision";
    }

    grouping multipart-header {
        uses ofproto:ofHeader;

        leaf request-more {
            type boolean;
            default false;
        }
    }

    container multipart-reply {
        uses multipart-header;

        choice multipart-reply-body {
        }
    }

    container multipart-request {
        uses multipart-header;

        choice multipart-request-body {
        }
    }
}
