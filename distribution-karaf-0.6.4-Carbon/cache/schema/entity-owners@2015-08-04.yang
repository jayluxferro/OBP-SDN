module entity-owners {
    yang-version 1;
    namespace "urn:opendaylight:params:xml:ns:yang:controller:md:sal:clustering:entity-owners";
    prefix "entity-owners";

    description
        "This module contains the base YANG definitions for
        an implementation of the EntityOwnershipService which stores
        entity ownership information in the data store";

    revision "2015-08-04" {
        description "Initial revision.";
    }

    container entity-owners {

        // A list of all entities grouped by type
        list entity-type {
            key type;
            leaf type {
                type string;
            }

            list entity {
                key id;

                leaf id {
                    type instance-identifier;
                }

                leaf owner {
                    type string;
                }

                // A list of all the candidates that would like to own the entity
                list candidate {
                    key name;
                    ordered-by user;

                    leaf name {
                        type string;
                    }
                }
            }
        }
    }
}
