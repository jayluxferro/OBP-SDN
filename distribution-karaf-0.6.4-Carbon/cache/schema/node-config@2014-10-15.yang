module node-config {
    namespace "urn:opendaylight:module:config";
    prefix node-config;

    import flow-capable-transaction {prefix tr; revision-date "2015-03-04";}
    import opendaylight-inventory {prefix inv;revision-date "2013-08-19";}

    description "Openflow initial device config.";

    revision "2014-10-15" {
        description "Initial revision
          + simplified node-context-ref in rpc input";
    }

    grouping node-config {
        description "Openflow device initial configuration structure.";
        
        leaf flag {
            type string;
            description "Switch config flag. Expected values FRAGNORMAL, OFPCFRAGDROP, OFPCFRAGREASM, OFPCFRAGMASK";
        }
        leaf miss-search-length{
            type uint16;
        }
    }

    rpc set-config {
        description "Sending initial configuration to device.";
        input {
            uses node-config;
            uses tr:transaction-aware;
            uses inv:node-context-ref;
        }
        output {
            uses tr:transaction-aware;
        }
    }
}
