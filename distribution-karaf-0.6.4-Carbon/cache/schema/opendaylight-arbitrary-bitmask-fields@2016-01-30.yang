module opendaylight-arbitrary-bitmask-fields {
    namespace "urn:opendaylight:arbitrary:bitmask:fields";
    prefix "mask";

    import ietf-inet-types {prefix inet; revision-date "2013-07-15";}
    import ietf-yang-types {prefix yang; revision-date "2013-07-15";}

    revision "2016-01-30" {
        description "Initial revision of match types";
    }

    grouping "ipv4-match-arbitrary-bitmask-fields" {

        leaf ipv4-source-address-no-mask {
            description "IPv4 source address with no mask.";
            type inet:ipv4-address;
        }

        leaf ipv4-destination-address-no-mask {
            description "IPv4 destination address with no mask.";
            type inet:ipv4-address;
        }

        leaf ipv4-source-arbitrary-bitmask {
            description "Arbitrary bit mask of IPv4 source address.";
            type yang:dotted-quad;
        }

        leaf ipv4-destination-arbitrary-bitmask {
            description "Arbitrary bit mask of IPv4 destination address.";
            type yang:dotted-quad;
        }
    }
}
