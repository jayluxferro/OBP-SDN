module subscribe-to-notification {

    yang-version 1;
    namespace "subscribe:to:notification";
    prefix "subs-to-notifi";

    description
        "Added input parameters to rpc create-data-change-event-subscription and to create-notification-stream";

    revision "2016-10-28" {
    }

    container "notifi"{
        leaf "location"{
            type string;
        }
    }
}
