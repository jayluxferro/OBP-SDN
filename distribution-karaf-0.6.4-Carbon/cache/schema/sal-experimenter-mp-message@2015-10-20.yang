module sal-experimenter-mp-message  {
    namespace "urn:opendaylight:experimenter-mp-message:service";
    prefix exp-mp-msg;

    import opendaylight-inventory {prefix inv;revision-date "2013-08-19";}
    import openflowplugin-experimenter-types {prefix exp-type;revision-date "2015-10-20";}

    description "Openflow multipart experimenter message service.";

    revision "2015-10-20" {
        description "Initial revision of experimenter multipart message service";
    }

    rpc send-experimenter-mp-request {
        description "Send experimenter multipart request to device, expecting reply.";
        input {
            uses "inv:node-context-ref";
            uses exp-type:experimenter-core-message;
        }
        output {
            list experimenter-core-message-item {
                uses exp-type:experimenter-core-message;
            }
        }
    }
}
