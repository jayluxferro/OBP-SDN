module aaa {
    yang-version 1;
    namespace "urn:opendaylight:params:xml:ns:yang:aaa";
    prefix "aaa";

    revision "2016-12-14" {
        description "Initial revision of aaa model";
    }

    grouping http-permission {
        leaf resource {
            type string;
            default "*";
        }
        list permissions {
            leaf-list actions {
                type enumeration {
                    enum get;
                    enum put;
                    enum post;
                    enum patch;
                    enum delete;
                }
            }
            leaf role {
                type string;
            }
        }
        leaf description {
            type string;
            default "";
        }
    }

    container http-authorization {

        container policies {
            list policies {
                key "resource";
                uses http-permission;
                ordered-by user;
            }
        }
    }
}
