module opendaylight-rest-connector {
    yang-version 1;
    namespace "urn:opendaylight:params:xml:ns:yang:controller:md:sal:rest:connector";
    prefix "md-sal-rest-connector";

    import config { prefix config; revision-date 2013-04-05; }
    import opendaylight-md-sal-dom {prefix dom; revision-date 2013-10-28;}
    import opendaylight-md-sal-binding {prefix sal; revision-date 2013-10-28;}
    import ietf-inet-types {prefix inet; revision-date 2013-07-15;}
 
    description
        "Service definition for Rest Connector";
 
    revision "2014-07-24" {
        description
            "Initial revision";
    }
    
    identity rest-connector {
        base "config:service-type";
        config:java-class "org.opendaylight.netconf.sal.rest.api.RestConnector";
    }
    
    identity rest-connector-impl {
        base config:module-type;
        config:provided-service rest-connector;
        config:java-name-prefix RestConnector;
    }
    
    grouping statistics {
        leaf received-requests {
           type uint64;
        }

        leaf successful-responses {
            type uint64;
        }

        leaf failed-responses {
            type uint64;
        }
    }

    augment "/config:modules/config:module/config:configuration" {
        case rest-connector-impl {
            when "/config:modules/config:module/config:type = 'rest-connector-impl'";
            leaf websocket-address {
                mandatory true;
                type inet:ipv4-address;
            }
            leaf websocket-port {
                mandatory true;
                type inet:port-number;
            }
            container dom-broker {
                uses config:service-ref {
                    refine type {
                        mandatory true;
                        config:required-identity dom:dom-broker-osgi-registry;
                    }
                }
            }
        }
    }
    
    augment "/config:modules/config:module/config:state" {
        case rest-connector-impl {
            when "/config:modules/config:module/config:type = 'rest-connector-impl'";
            container rpcs {
                uses statistics;
            }

            container config {
                container get {
                    uses statistics;
                }
                
                container post {
                    uses statistics;
                }
                
                container put {
                    uses statistics;
                }
                
                container delete {
                    uses statistics;
                }
            }

            container operational {
                container get {
                    uses statistics;
                }
            }
        }
    }
}
